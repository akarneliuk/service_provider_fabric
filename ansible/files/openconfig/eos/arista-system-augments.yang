module "arista-system-augments" {
	namespace "http://arista.com/yang/openconfig/system/augments";
	prefix "arista-system-augments";
	import "openconfig-system" {
		prefix "oc-sys";
	}
	import "openconfig-network-instance" {
		prefix "oc-ni";
	}
	organization "Arista Networks, Inc.";
	contact "Arista Networks, Inc.
	         Product Support";
	description "This module contains OpenConfig system augments in Arista EOS.
	             Copyright (c) 2018 Arista Networks, Inc. All rights reserved.";
	revision "2018-06-03" {
		description "Initial augment file.";
	}
	augment "/oc-sys:system/oc-sys:dns/oc-sys:config" {
		leaf "network-instance" {
			type "oc-ni:network-instance-ref";
			description "The network instance where the DNS servers are configured.";
		}
	}
	augment "/oc-sys:system/oc-sys:dns/oc-sys:state" {
		leaf "network-instance" {
			type "oc-ni:network-instance-ref";
			description "The network instance where the DNS servers are configured.";
		}
	}
}
