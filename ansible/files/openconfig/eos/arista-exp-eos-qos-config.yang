module "arista-exp-eos-qos-config" {
	yang-version "1";
	namespace "http://arista.com/yang/experimental/eos/qos/config";
	prefix "qos-config-exp";
	import "arista-eos-types" {
		prefix "eos-types";
	}
	import "arista-exp-eos" {
		prefix "eos-exp";
	}
	import "arista-exp-eos-qos" {
		prefix "qos-exp";
	}
	organization "Arista Networks &lt;http://arista.com/&gt;";
	description "Models for qos config subsystem of Arista EOS
	             Copyright (c) 2017 Arista Networks, Inc. All rights reserved.";
	revision "2017-09-26" {
		description "Initial revision";
	}
	augment "/eos-exp:arista/eos-exp:eos/qos-exp:qos" {
		container "input" {
			description "Path: /Sysdb/qos/input, Type: directory Tac::Dir";
			container "config" {
				description "Path: /Sysdb/qos/input/config, Type: directory Tac::Dir";
				container "cli" {
					description "Path: /Sysdb/qos/input/config/cli, Type: entity Qos::Input::Config";
					uses "Qos-Input-Config";
				}
			}
		}
	}
	grouping "Pfc-PortConfig" {
		description "Type: Pfc::PortConfig";
		leaf "enabled" {
			type "boolean";
			description "Path: &lt;Pfc::PortConfig&gt;/enabled, Type: bool";
		}
		container "portTimerConfig" {
			description "Path: &lt;Pfc::PortConfig&gt;/portTimerConfig, Type: value Pfc::PortTimerConfig";
			uses "Pfc-PortTimerConfig";
		}
		leaf "portWatchdogVersion" {
			type "uint32";
			description "Path: &lt;Pfc::PortConfig&gt;/portWatchdogVersion, Type: U32";
		}
		leaf "priorities" {
			type "uint8";
			description "Path: &lt;Pfc::PortConfig&gt;/priorities, Type: U8";
		}
		leaf "watchdogEnabled" {
			type "boolean";
			description "Path: &lt;Pfc::PortConfig&gt;/watchdogEnabled, Type: bool";
		}
		leaf "watchdogPortAction" {
			type "Pfc-WatchdogAction";
			description "Path: &lt;Pfc::PortConfig&gt;/watchdogPortAction, Type: enum Pfc::WatchdogAction";
		}
	}
	grouping "Pfc-PortTimerConfig" {
		description "Type: Pfc::PortTimerConfig";
		leaf "portWatchdogOperPollingInterval" {
			type "eos-types:double";
			description "Path: &lt;Pfc::PortTimerConfig&gt;/portWatchdogOperPollingInterval, Type: double";
		}
		leaf "portWatchdogPollingInterval" {
			type "eos-types:double";
			description "Path: &lt;Pfc::PortTimerConfig&gt;/portWatchdogPollingInterval, Type: double";
		}
		container "portWatchdogRecoveryCfg" {
			description "Path: &lt;Pfc::PortTimerConfig&gt;/portWatchdogRecoveryCfg, Type: value Pfc::WatchdogRecoveryConfig";
			uses "Pfc-WatchdogRecoveryConfig";
		}
		leaf "portWatchdogTimeout" {
			type "eos-types:double";
			description "Path: &lt;Pfc::PortTimerConfig&gt;/portWatchdogTimeout, Type: double";
		}
		leaf "usePerPortTimerValues" {
			type "boolean";
			description "Path: &lt;Pfc::PortTimerConfig&gt;/usePerPortTimerValues, Type: bool";
		}
	}
	typedef "Pfc-WatchdogAction" {
		type "enumeration" {
			enum "drop" {
				description "Type: Pfc::WatchdogAction, Name: drop, Value: 2";
			}
			enum "errdisable" {
				description "Type: Pfc::WatchdogAction, Name: errdisable, Value: 1";
			}
			enum "invalid" {
				description "Type: Pfc::WatchdogAction, Name: invalid, Value: 0";
			}
			enum "notifyOnly" {
				description "Type: Pfc::WatchdogAction, Name: notifyOnly, Value: 3";
			}
		}
		description "Type: Pfc::WatchdogAction";
	}
	grouping "Pfc-WatchdogRecoveryConfig" {
		description "Type: Pfc::WatchdogRecoveryConfig";
		leaf "forcedRecovery" {
			type "boolean";
			description "Path: &lt;Pfc::WatchdogRecoveryConfig&gt;/forcedRecovery, Type: bool";
		}
		leaf "recoveryTime" {
			type "eos-types:double";
			description "Path: &lt;Pfc::WatchdogRecoveryConfig&gt;/recoveryTime, Type: double";
		}
	}
	typedef "Qos-Direction" {
		type "enumeration" {
			enum "input" {
				description "Type: Qos::Direction, Name: input, Value: 0";
			}
			enum "output" {
				description "Type: Qos::Direction, Name: output, Value: 1";
			}
		}
		description "Type: Qos::Direction";
	}
	grouping "Qos-EcnDelayThreshold" {
		description "Type: Qos::EcnDelayThreshold";
		leaf "threshold" {
			type "uint32";
			description "Path: &lt;Qos::EcnDelayThreshold&gt;/threshold, Type: value Qos::EcnDelayThresholdValue";
		}
		leaf "unit" {
			type "Qos-EcnDelayThresholdUnit";
			description "Path: &lt;Qos::EcnDelayThreshold&gt;/unit, Type: enum Qos::EcnDelayThresholdUnit";
		}
	}
	typedef "Qos-EcnDelayThresholdUnit" {
		type "enumeration" {
			enum "ecnDelayThresholdInvalidUnit" {
				description "Type: Qos::EcnDelayThresholdUnit, Name: ecnDelayThresholdInvalidUnit, Value: 1";
			}
			enum "ecnDelayThresholdNs" {
				description "Type: Qos::EcnDelayThresholdUnit, Name: ecnDelayThresholdNs, Value: 0";
			}
		}
		description "Type: Qos::EcnDelayThresholdUnit";
	}
	grouping "Qos-EcnWredConfig" {
		description "Type: Qos::EcnWredConfig";
		leaf "maxDroprate" {
			type "uint8";
			description "Path: &lt;Qos::EcnWredConfig&gt;/maxDroprate, Type: value Qos::Percent";
		}
		leaf "maxThd" {
			type "uint32";
			description "Path: &lt;Qos::EcnWredConfig&gt;/maxThd, Type: value Qos::QueueThreshold";
		}
		leaf "minThd" {
			type "uint32";
			description "Path: &lt;Qos::EcnWredConfig&gt;/minThd, Type: value Qos::QueueThreshold";
		}
		leaf "unit" {
			type "Qos-QueueThresholdUnit";
			description "Path: &lt;Qos::EcnWredConfig&gt;/unit, Type: enum Qos::QueueThresholdUnit";
		}
		leaf "weight" {
			type "uint32";
			description "Path: &lt;Qos::EcnWredConfig&gt;/weight, Type: value Qos::Weight";
		}
	}
	grouping "Qos-GuaranteedBw" {
		description "Type: Qos::GuaranteedBw";
		leaf "bw" {
			type "uint32";
			description "Path: &lt;Qos::GuaranteedBw&gt;/bw, Type: value Qos::GuaranteedBwVal";
		}
		leaf "unit" {
			type "Qos-GuaranteedBwUnit";
			description "Path: &lt;Qos::GuaranteedBw&gt;/unit, Type: enum Qos::GuaranteedBwUnit";
		}
	}
	typedef "Qos-GuaranteedBwUnit" {
		type "enumeration" {
			enum "guaranteedBwKbps" {
				description "Type: Qos::GuaranteedBwUnit, Name: guaranteedBwKbps, Value: 0";
			}
			enum "guaranteedBwPercent" {
				description "Type: Qos::GuaranteedBwUnit, Name: guaranteedBwPercent, Value: 2";
			}
			enum "guaranteedBwPps" {
				description "Type: Qos::GuaranteedBwUnit, Name: guaranteedBwPps, Value: 1";
			}
		}
		description "Type: Qos::GuaranteedBwUnit";
	}
	grouping "Qos-Input-Config" {
		description "Type: Qos::Input::Config";
		leaf "agentName" {
			type "string";
			description "Path: &lt;Qos::Input::Config&gt;/agentName, Type: Tac::String";
		}
		leaf "configPriority" {
			type "uint32";
			description "Path: &lt;Qos::Input::Config&gt;/configPriority, Type: U32";
		}
		leaf "cosRewriteEnabled" {
			type "Qos-RewriteEnableMode";
			description "Path: &lt;Qos::Input::Config&gt;/cosRewriteEnabled, Type: enum Qos::RewriteEnableMode";
		}
		list "cosToTcMap" {
			key "index";
			description "Path: &lt;Qos::Input::Config&gt;/cosToTcMap, Type: [value Qos::Cos]value Qos::TrafficClass";
			leaf "index" {
				type "uint8";
				description "Path: &lt;Qos::Input::Config&gt;/cosToTcMap/&lt;!External index&gt;, Type: value Qos::Cos";
			}
			leaf "value" {
				type "uint8";
				description "Path: &lt;Qos::Input::Config&gt;/cosToTcMap/&lt;index&gt;, Type: value Qos::TrafficClass";
			}
		}
		leaf "dscpRewriteEnabled" {
			type "boolean";
			description "Path: &lt;Qos::Input::Config&gt;/dscpRewriteEnabled, Type: bool";
		}
		list "dscpToTcMap" {
			key "index";
			description "Path: &lt;Qos::Input::Config&gt;/dscpToTcMap, Type: [value Qos::Dscp]value Qos::TrafficClass";
			leaf "index" {
				type "uint8";
				description "Path: &lt;Qos::Input::Config&gt;/dscpToTcMap/&lt;!External index&gt;, Type: value Qos::Dscp";
			}
			leaf "value" {
				type "uint8";
				description "Path: &lt;Qos::Input::Config&gt;/dscpToTcMap/&lt;index&gt;, Type: value Qos::TrafficClass";
			}
		}
		leaf "ecnAllowNonEct" {
			type "boolean";
			description "Path: &lt;Qos::Input::Config&gt;/ecnAllowNonEct, Type: bool";
		}
		container "ecnDelayThreshold" {
			description "Path: &lt;Qos::Input::Config&gt;/ecnDelayThreshold, Type: value Qos::EcnDelayThreshold";
			uses "Qos-EcnDelayThreshold";
		}
		container "globalEcnConfig" {
			description "Path: &lt;Qos::Input::Config&gt;/globalEcnConfig, Type: entity Qos::EcnWredConfig";
			uses "Qos-EcnWredConfig";
		}
		leaf "hwConfigVerificationEnabled" {
			type "boolean";
			description "Path: &lt;Qos::Input::Config&gt;/hwConfigVerificationEnabled, Type: bool";
		}
		list "hwMonitoredPri" {
			key "index";
			description "Path: &lt;Qos::Input::Config&gt;/hwMonitoredPri, Type: [U8]bool";
			leaf "index" {
				type "uint8";
				description "Path: &lt;Qos::Input::Config&gt;/hwMonitoredPri/&lt;!External index&gt;, Type: U8";
			}
			leaf "value" {
				type "boolean";
				description "Path: &lt;Qos::Input::Config&gt;/hwMonitoredPri/&lt;index&gt;, Type: bool";
			}
		}
		list "intfConfig" {
			key "intfId";
			description "Path: &lt;Qos::Input::Config&gt;/intfConfig, Type: ['intfId' value Arnet::IntfId]entity Qos::IntfConfig";
			uses "Qos-IntfConfig";
		}
		leaf "intfConfigPriority" {
			type "uint32";
			description "Path: &lt;Qos::Input::Config&gt;/intfConfigPriority, Type: U32";
		}
		leaf "pfcGlobalEnabled" {
			type "boolean";
			description "Path: &lt;Qos::Input::Config&gt;/pfcGlobalEnabled, Type: bool";
		}
		list "servicePolicyConfig" {
			key "key-direction key-pmapName key-type";
			description "Path: &lt;Qos::Input::Config&gt;/servicePolicyConfig, Type: ['key' value Qos::ServicePolicyKey]entity Qos::ServicePolicyConfig";
			leaf "key-direction" {
				type "Qos-Direction";
				description "Path: &lt;Qos::ServicePolicyKey&gt;/direction, Type: enum Qos::Direction";
			}
			leaf "key-pmapName" {
				type "string";
				description "Path: &lt;Qos::ServicePolicyKey&gt;/pmapName, Type: Tac::Name";
			}
			leaf "key-type" {
				type "Qos-MapType";
				description "Path: &lt;Qos::ServicePolicyKey&gt;/type, Type: enum Qos::MapType";
			}
			leaf "clearCountersTime" {
				type "eos-types:double";
				description "Path: &lt;Qos::ServicePolicyConfig&gt;/clearCountersTime, Type: double";
			}
			list "intfIds" {
				key "index";
				description "Path: &lt;Qos::ServicePolicyConfig&gt;/intfIds, Type: [value Arnet::IntfId]bool";
				leaf "index" {
					type "eos-types:Arnet-IntfId";
					description "Path: &lt;Qos::ServicePolicyConfig&gt;/intfIds/&lt;!External index&gt;, Type: value Arnet::IntfId";
				}
				leaf "value" {
					type "boolean";
					description "Path: &lt;Qos::ServicePolicyConfig&gt;/intfIds/&lt;index&gt;, Type: bool";
				}
			}
		}
		list "tcToCosMap" {
			key "index";
			description "Path: &lt;Qos::Input::Config&gt;/tcToCosMap, Type: [value Qos::TrafficClass]value Qos::Cos";
			leaf "index" {
				type "uint8";
				description "Path: &lt;Qos::Input::Config&gt;/tcToCosMap/&lt;!External index&gt;, Type: value Qos::TrafficClass";
			}
			leaf "value" {
				type "uint8";
				description "Path: &lt;Qos::Input::Config&gt;/tcToCosMap/&lt;index&gt;, Type: value Qos::Cos";
			}
		}
		list "tcToDscpMap" {
			key "index";
			description "Path: &lt;Qos::Input::Config&gt;/tcToDscpMap, Type: [value Qos::TrafficClass]value Qos::Dscp";
			leaf "index" {
				type "uint8";
				description "Path: &lt;Qos::Input::Config&gt;/tcToDscpMap/&lt;!External index&gt;, Type: value Qos::TrafficClass";
			}
			leaf "value" {
				type "uint8";
				description "Path: &lt;Qos::Input::Config&gt;/tcToDscpMap/&lt;index&gt;, Type: value Qos::Dscp";
			}
		}
		list "tcToMcTxQueueMap" {
			key "index";
			description "Path: &lt;Qos::Input::Config&gt;/tcToMcTxQueueMap, Type: [value Qos::TrafficClass]value Qos::TxQueueId";
			leaf "index" {
				type "uint8";
				description "Path: &lt;Qos::Input::Config&gt;/tcToMcTxQueueMap/&lt;!External index&gt;, Type: value Qos::TrafficClass";
			}
			leaf "value" {
				type "uint8";
				description "Path: &lt;Qos::Input::Config&gt;/tcToMcTxQueueMap/&lt;index&gt;, Type: value Qos::TxQueueId";
			}
		}
		list "tcToTxQueueMap" {
			key "index";
			description "Path: &lt;Qos::Input::Config&gt;/tcToTxQueueMap, Type: [value Qos::TrafficClass]value Qos::TxQueueId";
			leaf "index" {
				type "uint8";
				description "Path: &lt;Qos::Input::Config&gt;/tcToTxQueueMap/&lt;!External index&gt;, Type: value Qos::TrafficClass";
			}
			leaf "value" {
				type "uint8";
				description "Path: &lt;Qos::Input::Config&gt;/tcToTxQueueMap/&lt;index&gt;, Type: value Qos::TxQueueId";
			}
		}
		leaf "watchdogAction" {
			type "Pfc-WatchdogAction";
			description "Path: &lt;Qos::Input::Config&gt;/watchdogAction, Type: enum Pfc::WatchdogAction";
		}
		leaf "watchdogNonDisruptivePriorities" {
			type "uint8";
			description "Path: &lt;Qos::Input::Config&gt;/watchdogNonDisruptivePriorities, Type: U8";
		}
		leaf "watchdogPollingInterval" {
			type "eos-types:double";
			description "Path: &lt;Qos::Input::Config&gt;/watchdogPollingInterval, Type: double";
		}
		container "watchdogRecoveryCfg" {
			description "Path: &lt;Qos::Input::Config&gt;/watchdogRecoveryCfg, Type: value Pfc::WatchdogRecoveryConfig";
			uses "Pfc-WatchdogRecoveryConfig";
		}
		leaf "watchdogTimeout" {
			type "eos-types:double";
			description "Path: &lt;Qos::Input::Config&gt;/watchdogTimeout, Type: double";
		}
	}
	grouping "Qos-IntfConfig" {
		description "Type: Qos::IntfConfig";
		leaf "defaultCos" {
			type "uint8";
			description "Path: &lt;Qos::IntfConfig&gt;/defaultCos, Type: value Qos::Cos";
		}
		leaf "defaultDscp" {
			type "uint8";
			description "Path: &lt;Qos::IntfConfig&gt;/defaultDscp, Type: value Qos::Dscp";
		}
		leaf "fabricPfcDlb" {
			type "uint8";
			description "Path: &lt;Qos::IntfConfig&gt;/fabricPfcDlb, Type: U8";
		}
		leaf "intfId" {
			type "eos-types:Arnet-IntfId";
			description "Path: &lt;Qos::IntfConfig&gt;/intfId, Type: value Arnet::IntfId";
		}
		container "pfcPortConfig" {
			description "Path: &lt;Qos::IntfConfig&gt;/pfcPortConfig, Type: entity Pfc::PortConfig";
			uses "Pfc-PortConfig";
		}
		container "shapeRate" {
			description "Path: &lt;Qos::IntfConfig&gt;/shapeRate, Type: value Qos::ShapeRate";
			uses "Qos-ShapeRate";
		}
		leaf "trustMode" {
			type "Qos-TrustMode";
			description "Path: &lt;Qos::IntfConfig&gt;/trustMode, Type: enum Qos::TrustMode";
		}
		list "txQueueConfig" {
			key "txQueue-id txQueue-type";
			description "Path: &lt;Qos::IntfConfig&gt;/txQueueConfig, Type: ['txQueue' value Qos::TxQueue]entity Qos::TxQueueConfig";
			leaf "txQueue-id" {
				type "uint8";
				description "Path: &lt;Qos::TxQueue&gt;/id, Type: value Qos::TxQueueId";
			}
			leaf "txQueue-type" {
				type "Qos-QueueType";
				description "Path: &lt;Qos::TxQueue&gt;/type, Type: enum Qos::QueueType";
			}
			leaf "bandwidth" {
				type "uint8";
				description "Path: &lt;Qos::TxQueueConfig&gt;/bandwidth, Type: value Qos::Percent";
			}
			leaf "delayEcnEnabled" {
				type "boolean";
				description "Path: &lt;Qos::TxQueueConfig&gt;/delayEcnEnabled, Type: bool";
			}
			container "ecnConfig" {
				description "Path: &lt;Qos::TxQueueConfig&gt;/ecnConfig, Type: entity Qos::EcnWredConfig";
				uses "Qos-EcnWredConfig";
			}
			container "ecnDelayThreshold" {
				description "Path: &lt;Qos::TxQueueConfig&gt;/ecnDelayThreshold, Type: value Qos::EcnDelayThreshold";
				uses "Qos-EcnDelayThreshold";
			}
			container "guaranteedBw" {
				description "Path: &lt;Qos::TxQueueConfig&gt;/guaranteedBw, Type: value Qos::GuaranteedBw";
				uses "Qos-GuaranteedBw";
			}
			container "nonEctConfig" {
				description "Path: &lt;Qos::TxQueueConfig&gt;/nonEctConfig, Type: entity Qos::EcnWredConfig";
				uses "Qos-EcnWredConfig";
			}
			leaf "priority" {
				type "Qos-TxQueuePriority";
				description "Path: &lt;Qos::TxQueueConfig&gt;/priority, Type: enum Qos::TxQueuePriority";
			}
			container "shapeRate" {
				description "Path: &lt;Qos::TxQueueConfig&gt;/shapeRate, Type: value Qos::ShapeRate";
				uses "Qos-ShapeRate";
			}
			container "wredConfig" {
				description "Path: &lt;Qos::TxQueueConfig&gt;/wredConfig, Type: entity Qos::EcnWredConfig";
				uses "Qos-EcnWredConfig";
			}
		}
	}
	typedef "Qos-MapType" {
		type "enumeration" {
			enum "mapControlPlane" {
				description "Type: Qos::MapType, Name: mapControlPlane, Value: 0";
			}
			enum "mapPdp" {
				description "Type: Qos::MapType, Name: mapPdp, Value: 2";
			}
			enum "mapQos" {
				description "Type: Qos::MapType, Name: mapQos, Value: 1";
			}
		}
		description "Type: Qos::MapType";
	}
	typedef "Qos-QueueThresholdUnit" {
		type "enumeration" {
			enum "bytes" {
				description "Type: Qos::QueueThresholdUnit, Name: bytes, Value: 0";
			}
			enum "kbytes" {
				description "Type: Qos::QueueThresholdUnit, Name: kbytes, Value: 1";
			}
			enum "mbytes" {
				description "Type: Qos::QueueThresholdUnit, Name: mbytes, Value: 2";
			}
			enum "segments" {
				description "Type: Qos::QueueThresholdUnit, Name: segments, Value: 3";
			}
		}
		description "Type: Qos::QueueThresholdUnit";
	}
	typedef "Qos-QueueType" {
		type "enumeration" {
			enum "mcq" {
				description "Type: Qos::QueueType, Name: mcq, Value: 1";
			}
			enum "ucq" {
				description "Type: Qos::QueueType, Name: ucq, Value: 0";
			}
			enum "unknown" {
				description "Type: Qos::QueueType, Name: unknown, Value: 2";
			}
		}
		description "Type: Qos::QueueType";
	}
	typedef "Qos-RewriteEnableMode" {
		type "enumeration" {
			enum "rewriteDisabled" {
				description "Type: Qos::RewriteEnableMode, Name: rewriteDisabled, Value: 2";
			}
			enum "rewriteEnabled" {
				description "Type: Qos::RewriteEnableMode, Name: rewriteEnabled, Value: 1";
			}
			enum "rewriteInvalid" {
				description "Type: Qos::RewriteEnableMode, Name: rewriteInvalid, Value: 0";
			}
		}
		description "Type: Qos::RewriteEnableMode";
	}
	grouping "Qos-ShapeRate" {
		description "Type: Qos::ShapeRate";
		leaf "rate" {
			type "uint32";
			description "Path: &lt;Qos::ShapeRate&gt;/rate, Type: value Qos::ShapeRateVal";
		}
		leaf "unit" {
			type "Qos-ShapeRateUnit";
			description "Path: &lt;Qos::ShapeRate&gt;/unit, Type: enum Qos::ShapeRateUnit";
		}
	}
	typedef "Qos-ShapeRateUnit" {
		type "enumeration" {
			enum "shapeRateKbps" {
				description "Type: Qos::ShapeRateUnit, Name: shapeRateKbps, Value: 0";
			}
			enum "shapeRatePps" {
				description "Type: Qos::ShapeRateUnit, Name: shapeRatePps, Value: 1";
			}
		}
		description "Type: Qos::ShapeRateUnit";
	}
	typedef "Qos-TrustMode" {
		type "enumeration" {
			enum "cos" {
				description "Type: Qos::TrustMode, Name: cos, Value: 0";
			}
			enum "dscp" {
				description "Type: Qos::TrustMode, Name: dscp, Value: 1";
			}
			enum "invalid" {
				description "Type: Qos::TrustMode, Name: invalid, Value: 3";
			}
			enum "untrusted" {
				description "Type: Qos::TrustMode, Name: untrusted, Value: 2";
			}
		}
		description "Type: Qos::TrustMode";
	}
	typedef "Qos-TxQueuePriority" {
		type "enumeration" {
			enum "priorityInvalid" {
				description "Type: Qos::TxQueuePriority, Name: priorityInvalid, Value: 2";
			}
			enum "priorityRoundRobin" {
				description "Type: Qos::TxQueuePriority, Name: priorityRoundRobin, Value: 0";
			}
			enum "priorityStrict" {
				description "Type: Qos::TxQueuePriority, Name: priorityStrict, Value: 1";
			}
		}
		description "Type: Qos::TxQueuePriority";
	}
}
