module "arista-mpls-deviations" {
	namespace "http://arista.com/yang/openconfig/mpls/deviations";
	prefix "arista-mpls-deviations";
	import "openconfig-network-instance" {
		prefix "oc-netinst";
	}
	organization "Arista Networks &lt;http://arista.com/&gt;";
	description "This module contains OpenConfig MPLS deviations in Arista EOS.
	             
	             Copyright (c) 2018 Arista Networks, Inc. All rights reserved.";
	revision "2018-03-19" {
		description "Initial deviation file.";
	}
	deviation "/oc-netinst:network-instances/oc-netinst:network-instance/oc-netinst:mpls/oc-netinst:signaling-protocols/oc-netinst:segment-routing/oc-netinst:interfaces/oc-netinst:interface/oc-netinst:sid-counters/oc-netinst:sid-counter/oc-netinst:state/oc-netinst:in-octets" {
		description "in-octets per interface per label is not supported in EOS";
		deviate "not-supported";
	}
	deviation "/oc-netinst:network-instances/oc-netinst:network-instance/oc-netinst:mpls/oc-netinst:signaling-protocols/oc-netinst:segment-routing/oc-netinst:interfaces/oc-netinst:interface/oc-netinst:sid-counters/oc-netinst:sid-counter/oc-netinst:state/oc-netinst:in-pkts" {
		description "in-pkts per interface per label is not supported in EOS";
		deviate "not-supported";
	}
	deviation "/oc-netinst:network-instances/oc-netinst:network-instance/oc-netinst:mpls/oc-netinst:signaling-protocols/oc-netinst:segment-routing/oc-netinst:interfaces/oc-netinst:interface/oc-netinst:sid-counters/oc-netinst:sid-counter/oc-netinst:state/oc-netinst:out-octets" {
		description "out-octets per interface per label is not supported in EOS";
		deviate "not-supported";
	}
	deviation "/oc-netinst:network-instances/oc-netinst:network-instance/oc-netinst:mpls/oc-netinst:signaling-protocols/oc-netinst:segment-routing/oc-netinst:interfaces/oc-netinst:interface/oc-netinst:sid-counters/oc-netinst:sid-counter/oc-netinst:state/oc-netinst:out-pkts" {
		description "out-pkts per interface per label is not supported in EOS";
		deviate "not-supported";
	}
	deviation "/oc-netinst:network-instances/oc-netinst:network-instance/oc-netinst:mpls/oc-netinst:signaling-protocols/oc-netinst:segment-routing/oc-netinst:interfaces/oc-netinst:interface/oc-netinst:sid-counters/oc-netinst:sid-counter/oc-netinst:forwarding-classes/oc-netinst:forwarding-class/oc-netinst:state/oc-netinst:in-octets" {
		description "in-octets per interface per label per forwarding-class is not supported in EOS";
		deviate "not-supported";
	}
	deviation "/oc-netinst:network-instances/oc-netinst:network-instance/oc-netinst:mpls/oc-netinst:signaling-protocols/oc-netinst:segment-routing/oc-netinst:interfaces/oc-netinst:interface/oc-netinst:sid-counters/oc-netinst:sid-counter/oc-netinst:forwarding-classes/oc-netinst:forwarding-class/oc-netinst:state/oc-netinst:in-pkts" {
		description "in-pkts per interface per label per forwarding-class is not supported in EOS";
		deviate "not-supported";
	}
	deviation "/oc-netinst:network-instances/oc-netinst:network-instance/oc-netinst:mpls/oc-netinst:signaling-protocols/oc-netinst:segment-routing/oc-netinst:interfaces/oc-netinst:interface/oc-netinst:sid-counters/oc-netinst:sid-counter/oc-netinst:forwarding-classes/oc-netinst:forwarding-class/oc-netinst:state/oc-netinst:out-octets" {
		description "out-octets per interface per label per forwarding-class is not supported in EOS";
		deviate "not-supported";
	}
	deviation "/oc-netinst:network-instances/oc-netinst:network-instance/oc-netinst:mpls/oc-netinst:signaling-protocols/oc-netinst:segment-routing/oc-netinst:interfaces/oc-netinst:interface/oc-netinst:sid-counters/oc-netinst:sid-counter/oc-netinst:forwarding-classes/oc-netinst:forwarding-class/oc-netinst:state/oc-netinst:out-pkts" {
		description "out-pkts per interface per label per forwarding-class is not supported in EOS";
		deviate "not-supported";
	}
}
