module "arista-lacp-deviations" {
	namespace "http://arista.com/yang/openconfig/lacp/deviations";
	prefix "arista-lacp-deviations";
	import "openconfig-lacp" {
		prefix "oc-lacp";
	}
	organization "Arista Networks, Inc.";
	contact "Arista Networks, Inc.
	         Product Support";
	description "This module contains OpenConfig lacp deviations in Arista EOS.
	             
	             Copyright (c) 2017 Arista Networks, Inc. All rights reserved.";
	revision "2017-09-07" {
		description "Initial deviations file.";
	}
	deviation "/oc-lacp:lacp/oc-lacp:config/oc-lacp:system-priority" {
		description "system-priority has a default value of 0x8000 in EOS";
		deviate "add" {
			default "32768";
		}
	}
	deviation "/oc-lacp:lacp/oc-lacp:interfaces/oc-lacp:interface/oc-lacp:config/oc-lacp:lacp-mode" {
		description "EOS does not support port channel level lacp-mode";
		deviate "not-supported";
	}
	deviation "/oc-lacp:lacp/oc-lacp:interfaces/oc-lacp:interface/oc-lacp:config/oc-lacp:system-priority" {
		description "EOS does not support port channel level system priority";
		deviate "not-supported";
	}
	deviation "/oc-lacp:lacp/oc-lacp:interfaces/oc-lacp:interface/oc-lacp:state/oc-lacp:lacp-mode" {
		description "EOS does not support port channel level lacp-mode";
		deviate "not-supported";
	}
	deviation "/oc-lacp:lacp/oc-lacp:interfaces/oc-lacp:interface/oc-lacp:state/oc-lacp:system-priority" {
		description "EOS does not support port channel level system priority";
		deviate "not-supported";
	}
	deviation "/oc-lacp:lacp/oc-lacp:interfaces/oc-lacp:interface/oc-lacp:members/oc-lacp:member/oc-lacp:state/oc-lacp:counters/oc-lacp:lacp-rx-errors" {
		description "EOS does not support LACP RX errors";
		deviate "not-supported";
	}
	deviation "/oc-lacp:lacp/oc-lacp:interfaces/oc-lacp:interface/oc-lacp:members/oc-lacp:member/oc-lacp:state/oc-lacp:counters/oc-lacp:lacp-tx-errors" {
		description "EOS does not support LACP TX errors";
		deviate "not-supported";
	}
	deviation "/oc-lacp:lacp/oc-lacp:interfaces/oc-lacp:interface/oc-lacp:members/oc-lacp:member/oc-lacp:state/oc-lacp:counters/oc-lacp:lacp-unknown-errors" {
		description "EOS does not support LACP Unknown errors";
		deviate "not-supported";
	}
	deviation "/oc-lacp:lacp/oc-lacp:interfaces/oc-lacp:interface/oc-lacp:members/oc-lacp:member/oc-lacp:state/oc-lacp:counters/oc-lacp:lacp-errors" {
		description "EOS does not support LACP errors";
		deviate "not-supported";
	}
}
