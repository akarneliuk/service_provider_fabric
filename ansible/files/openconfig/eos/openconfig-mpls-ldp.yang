module "openconfig-mpls-ldp" {
	yang-version "1";
	namespace "http://openconfig.net/yang/ldp";
	prefix "ldp";
	import "openconfig-extensions" {
		prefix "oc-ext";
	}
	organization "OpenConfig working group";
	contact "OpenConfig working group
	         netopenconfig@googlegroups.com";
	description "Configuration of Label Distribution Protocol global and LSP-
	             specific parameters for IGP-congruent LSPs";
	oc-ext:openconfig-version "2.4.1";
	revision "2017-08-24" {
		description "Minor formatting fixes.";
		reference "2.4.1";
	}
	revision "2017-06-21" {
		description "Add TC bits typedef.";
		reference "2.4.0";
	}
	revision "2017-03-22" {
		description "Add RSVP calculated-absolute-subscription-bw";
		reference "2.3.0";
	}
	revision "2017-01-26" {
		description "Add RSVP Tspec, clarify units for RSVP, remove unused LDP";
		reference "2.2.0";
	}
	revision "2016-12-15" {
		description "Add additional MPLS parameters";
		reference "2.1.0";
	}
	revision "2016-09-01" {
		description "Revisions based on implementation feedback";
		reference "2.0.0";
	}
	revision "2016-08-08" {
		description "Public release of MPLS models";
		reference "1.0.1";
	}
	grouping "ldp-global" {
		description "global LDP signaling configuration";
		container "ldp" {
			description "LDP global signaling configuration";
		}
	}
	grouping "igp-tunnel-ldp" {
		description "common defintiions for LDP-signaled LSP tunnel
		             types";
	}
	grouping "igp-lsp-ldp-setup" {
		description "grouping for LDP setup attributes";
		container "ldp" {
			description "LDP signaling setup for IGP-congruent LSPs";
			uses "igp-tunnel-ldp";
		}
	}
}
