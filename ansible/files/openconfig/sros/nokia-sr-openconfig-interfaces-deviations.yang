module nokia-sr-openconfig-interfaces-deviations {

    namespace "urn:nokia.com:sros:ns:yang:sr:openconfig_interfaces_deviations";

    prefix "nokia-sr-oc-if-devs";

    import nokia-sros-yang-extensions     { prefix "sros-ext"; }
    import openconfig-extensions          { prefix "ocext"; }
    import openconfig-interfaces          { prefix "oc-if"; }
    import openconfig-types               { prefix "oc-types"; }
    import openconfig-yang-types          { prefix "oc-yang"; }

    sros-ext:sros-major-release "rel16";

    organization "Nokia";

    contact
        "Nokia SR OS Support
         Web: <http://www.nokia.com>";

    description
        "This module contains the list of deviations against the openconfig-interfaces
          module for the Nokia SR OS based routers.

         Copyright 2016 Nokia. All rights reserved. Reproduction of this document
         is authorized on the condition that the foregoing copyright notice is included.

         This nokia-sr-openconfig-interfaces-deviations YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2016-12-22";

    deviation /oc-if:interfaces/oc-if:interface/oc-if:config/oc-if:name {
        deviate replace {
            type string {
                pattern "system|loopback|
                lag-([1-9]|[1-9][0-9]|[1-7][0-9][0-9]|800)|
                (([1-9]|1[0-9]|20)/([1-9]|1[0-9])/([1-9]|[1-9][0-9]|1[0-5][0-9]|160))|
                (([1-9]|1[0-9]|20)/([1-9]|1[0-9])/(c([1-9]|[1-2][0-9]|3[0-6]))(/([1-9]|10)){0,1})";
                length 1..12;
            }
        }
    }

    deviation /oc-if:interfaces/oc-if:interface/oc-if:config/oc-if:mtu {
        deviate add {
            units bytes;
        }
        deviate replace {
            type uint16 {
                range 512..9212;
            }
        }
    }

    deviation /oc-if:interfaces/oc-if:interface/oc-if:config/oc-if:description {
        deviate replace {
            type string {
                length 1..160;
            }
        }
    }

    deviation /oc-if:interfaces/oc-if:interface/oc-if:state/oc-if:name {
        deviate replace {
            type string {
                pattern "system|loopback|
                lag-([1-9]|[1-9][0-9]|[1-7][0-9][0-9]|800)|
                (([1-9]|1[0-9]|20)/([1-9]|1[0-9])/([1-9]|[1-9][0-9]|1[0-5][0-9]|160))|
                (([1-9]|1[0-9]|20)/([1-9]|1[0-9])/(c([1-9]|[1-2][0-9]|3[0-6]))(/([1-9]|10)){0,1})";
                length 1..12;
            }
        }
    }

    deviation /oc-if:interfaces/oc-if:interface/oc-if:state/oc-if:mtu {
        deviate add {
            units bytes;
        }
        deviate replace {
            type uint16 {
                range 512..9212;
            }
        }
    }

    deviation /oc-if:interfaces/oc-if:interface/oc-if:state/oc-if:description {
        deviate replace {
            type string {
                length 1..160;
            }
        }
    }

    deviation /oc-if:interfaces/oc-if:interface/oc-if:hold-time/oc-if:config/oc-if:up {
        deviate replace {
            type uint32 {
                range 0..36000000;
            }
        }
    }

    deviation /oc-if:interfaces/oc-if:interface/oc-if:hold-time/oc-if:config/oc-if:down {
        deviate replace {
            type uint32 {
                range 0..36000000;
            }
        }
    }

    deviation /oc-if:interfaces/oc-if:interface/oc-if:hold-time/oc-if:state/oc-if:up {
        deviate replace {
            type uint32 {
                range 0..36000000;
            }
        }
    }

    deviation /oc-if:interfaces/oc-if:interface/oc-if:hold-time/oc-if:state/oc-if:down {
        deviate replace {
            type uint32 {
                range 0..36000000;
            }
        }
    }

    deviation /oc-if:interfaces/oc-if:interface/oc-if:subinterfaces/oc-if:subinterface/oc-if:config/oc-if:description {
        deviate replace {
            type string {
                length 1..160;
            }
        }
    }

    deviation /oc-if:interfaces/oc-if:interface/oc-if:subinterfaces/oc-if:subinterface/oc-if:state/oc-if:description {
        deviate replace {
            type string {
                length 1..160;
            }
        }
    }

    deviation /oc-if:interfaces/oc-if:interface/oc-if:subinterfaces/oc-if:subinterface/oc-if:state/oc-if:counters/oc-if:in-discards {
        deviate not-supported;
    }

    deviation /oc-if:interfaces/oc-if:interface/oc-if:subinterfaces/oc-if:subinterface/oc-if:state/oc-if:counters/oc-if:in-errors {
        deviate not-supported;
    }

    deviation /oc-if:interfaces/oc-if:interface/oc-if:subinterfaces/oc-if:subinterface/oc-if:state/oc-if:counters/oc-if:in-unknown-protos {
        deviate not-supported;
    }

    deviation /oc-if:interfaces/oc-if:interface/oc-if:subinterfaces/oc-if:subinterface/oc-if:state/oc-if:counters/oc-if:out-errors {
        deviate not-supported;
    }

}
