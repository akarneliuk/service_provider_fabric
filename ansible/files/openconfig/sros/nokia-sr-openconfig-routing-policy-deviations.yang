module nokia-sr-openconfig-routing-policy-deviations {

    namespace "urn:nokia.com:sros:ns:yang:sr:openconfig_routing_policy_deviations";

    prefix "nokia-sr-oc-rpol-devs";

    import nokia-sros-yang-extensions     { prefix "sros-ext"; }
    import openconfig-extensions          { prefix "ocext"; }
    import openconfig-inet-types          { prefix "oc-inet"; }
    import openconfig-interfaces          { prefix "oc-if"; }
    import openconfig-policy-types        { prefix "oc-pol-types"; }
    import openconfig-routing-policy      { prefix "oc-rpol"; }
    import openconfig-types               { prefix "oc-types"; }

    sros-ext:sros-major-release "rel16";

    organization "Nokia";

    contact
        "Nokia SR OS Support
         Web: <http://www.nokia.com>";

    description
        "This module contains the list of deviations against the openconfig-routing-policy
          module for the Nokia SR OS based routers.

         Copyright 2016 Nokia. All rights reserved. Reproduction of this document
         is authorized on the condition that the foregoing copyright notice is included.

         This nokia-sr-openconfig-routing-policy-deviations YANG module embodies Nokia's proprietary
         intellectual property. Nokia retains all title and ownership in the
         specification, including any revisions.

         Nokia grants all interested parties a non-exclusive license to use
         and distribute an unmodified copy of this specification in connection with
         management of Nokia products, and without fee, provided this
         copyright notice and license appear on all copies.

         This specification is supplied `as is', and Nokia makes no warranty,
         either express or implied, as to the use, operation, condition, or performance
         of the specification.";

    revision "2016-05-12";

    deviation /oc-rpol:routing-policy/oc-rpol:defined-sets/oc-rpol:prefix-sets/oc-rpol:prefix-set/oc-rpol:config/oc-rpol:name {
        description "Added limit to string length and will not accept all spaces.";
        deviate replace {
            type string {
                length 1..32;
            }
        }
    }

    deviation /oc-rpol:routing-policy/oc-rpol:defined-sets/oc-rpol:prefix-sets/oc-rpol:prefix-set/oc-rpol:state/oc-rpol:name {
        description "Added limit to string length and will not accept all spaces.";
        deviate replace {
            type string {
                length 1..32;
            }
        }
    }

    deviation /oc-rpol:routing-policy/oc-rpol:defined-sets/oc-rpol:prefix-sets/oc-rpol:prefix-set/oc-rpol:prefixes/oc-rpol:prefix/oc-rpol:config/oc-rpol:masklength-range {
        description "Added limit to string length and will not accept all spaces.";
        deviate replace {
            type string {
                length 4..8;
            }
        }
    }

    deviation /oc-rpol:routing-policy/oc-rpol:defined-sets/oc-rpol:prefix-sets/oc-rpol:prefix-set/oc-rpol:prefixes/oc-rpol:prefix/oc-rpol:state/oc-rpol:masklength-range {
        description "Added limit to string length and will not accept all spaces.";
        deviate replace {
            type string {
                length 4..8;
            }
        }
    }

    deviation /oc-rpol:routing-policy/oc-rpol:defined-sets/oc-rpol:neighbor-sets {
        deviate not-supported;
    }

    deviation /oc-rpol:routing-policy/oc-rpol:defined-sets/oc-rpol:tag-sets/oc-rpol:tag-set/oc-rpol:config/oc-rpol:tag-value {
        description "Added max limit of elements (1).";
        deviate add {
            max-elements 1;
        }
        deviate replace {
            type uint32;
        }
    }

    deviation /oc-rpol:routing-policy/oc-rpol:defined-sets/oc-rpol:tag-sets/oc-rpol:tag-set/oc-rpol:state/oc-rpol:tag-value {
        description "Added max limit of elements (1).";
        deviate add {
            max-elements 1;
        }
        deviate replace {
            type uint32;
        }
    }

    deviation /oc-rpol:routing-policy/oc-rpol:policy-definitions/oc-rpol:policy-definition/oc-rpol:config/oc-rpol:name {
        description "Added limit to string length and will not accept all spaces.";
        deviate replace {
            type string {
                length 1..64;
            }
        }
    }

    deviation /oc-rpol:routing-policy/oc-rpol:policy-definitions/oc-rpol:policy-definition/oc-rpol:state/oc-rpol:name {
        description "Added limit to string length and will not accept all spaces.";
        deviate replace {
            type string {
                length 1..64;
            }
        }
    }

    deviation /oc-rpol:routing-policy/oc-rpol:policy-definitions/oc-rpol:policy-definition/oc-rpol:statements/oc-rpol:statement/oc-rpol:config/oc-rpol:name {
        description "Added limit to string length and will not accept all spaces.";
        deviate replace {
            type string {
                length 1..64;
            }
        }
    }

    deviation /oc-rpol:routing-policy/oc-rpol:policy-definitions/oc-rpol:policy-definition/oc-rpol:statements/oc-rpol:statement/oc-rpol:state/oc-rpol:name {
        description "Added limit to string length and will not accept all spaces.";
        deviate replace {
            type string {
                length 1..64;
            }
        }
    }

    deviation /oc-rpol:routing-policy/oc-rpol:policy-definitions/oc-rpol:policy-definition/oc-rpol:statements/oc-rpol:statement/oc-rpol:conditions/oc-rpol:match-interface {
        deviate not-supported;
    }

    deviation /oc-rpol:routing-policy/oc-rpol:policy-definitions/oc-rpol:policy-definition/oc-rpol:statements/oc-rpol:statement/oc-rpol:conditions/oc-rpol:match-neighbor-set {
        deviate not-supported;
    }

    deviation /oc-rpol:routing-policy/oc-rpol:policy-definitions/oc-rpol:policy-definition/oc-rpol:statements/oc-rpol:statement {
        deviate add {
            max-elements 65536;
        }
    }

}
