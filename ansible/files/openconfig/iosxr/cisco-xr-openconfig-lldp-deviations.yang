module cisco-xr-openconfig-lldp-deviations {

  prefix  "lldpdevs";

  namespace "http://cisco.com/ns/yang/cisco-xr-openconfig-lldp-deviations";

  // import some basic types
  import openconfig-lldp { prefix oc-lldp; }

  organization "Cisco Systems, Inc.";

  contact
    "Cisco Systems, Inc.
     Customer Service

     Postal: 170 West Tasman Drive
     San Jose, CA 95134

     Tel: +1 800 553-NETS

     E-mail: cs-yang@cisco.com";

  description
    "This module contains a set of deviations for 
 
     openconfig-lldp.yang@2017-03-08 

     on Cisco IOS-XR devices.

     Copyright (c) 2016-2017 by Cisco Systems, Inc.
     All rights reserved.";

  revision "2017-03-08" {
    description
      "Initial revision applicable to IOS-XR 6.3.2";
  }

  deviation /oc-lldp:lldp/oc-lldp:config/oc-lldp:system-name {
    deviate not-supported;
  }

  deviation /oc-lldp:lldp/oc-lldp:config/oc-lldp:system-description {
    deviate not-supported;
  }

  deviation /oc-lldp:lldp/oc-lldp:config/oc-lldp:chassis-id {
    deviate not-supported;
  }

  deviation /oc-lldp:lldp/oc-lldp:config/oc-lldp:chassis-id-type {
    deviate not-supported;
  }

  deviation /oc-lldp:lldp/oc-lldp:state/oc-lldp:system-description {
    deviate not-supported;
  }

  deviation /oc-lldp:lldp/oc-lldp:state/oc-lldp:counters/oc-lldp:last-clear {
    deviate not-supported;
  }

  deviation  /oc-lldp:lldp/oc-lldp:state/oc-lldp:counters/oc-lldp:tlv-accepted {
    deviate not-supported;
  }

  deviation /oc-lldp:lldp/oc-lldp:interfaces/oc-lldp:interface/oc-lldp:state/oc-lldp:counters/oc-lldp:frame-in {
    deviate not-supported;
  }

  deviation /oc-lldp:lldp/oc-lldp:interfaces/oc-lldp:interface/oc-lldp:state/oc-lldp:counters/oc-lldp:frame-out {
    deviate not-supported;
  }

  deviation /oc-lldp:lldp/oc-lldp:interfaces/oc-lldp:interface/oc-lldp:state/oc-lldp:counters/oc-lldp:frame-error-in {
    deviate not-supported;
  }

  deviation /oc-lldp:lldp/oc-lldp:interfaces/oc-lldp:interface/oc-lldp:state/oc-lldp:counters/oc-lldp:frame-discard {
    deviate not-supported;
  }

  deviation /oc-lldp:lldp/oc-lldp:interfaces/oc-lldp:interface/oc-lldp:state/oc-lldp:counters/oc-lldp:tlv-discard {
    deviate not-supported;
  }

  deviation /oc-lldp:lldp/oc-lldp:interfaces/oc-lldp:interface/oc-lldp:state/oc-lldp:counters/oc-lldp:tlv-unknown {
    deviate not-supported;
  }

  deviation /oc-lldp:lldp/oc-lldp:interfaces/oc-lldp:interface/oc-lldp:state/oc-lldp:counters/oc-lldp:last-clear {
    deviate not-supported;
  }

  deviation /oc-lldp:lldp/oc-lldp:interfaces/oc-lldp:interface/oc-lldp:state/oc-lldp:counters/oc-lldp:frame-error-out {
    deviate not-supported;
  }

  deviation /oc-lldp:lldp/oc-lldp:interfaces/oc-lldp:interface/oc-lldp:neighbors/oc-lldp:neighbor/oc-lldp:state/oc-lldp:age{
    deviate not-supported;
  }

  deviation /oc-lldp:lldp/oc-lldp:interfaces/oc-lldp:interface/oc-lldp:neighbors/oc-lldp:neighbor/oc-lldp:state/oc-lldp:last-update{
    deviate not-supported;
  }
}
//total deviations:17
